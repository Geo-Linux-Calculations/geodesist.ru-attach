(defun c:3D3PCC (/ p1 p2 p3)
 (setq p1 (getpoint "Circle point #1: "))
 (setq p2 (getpoint "Circle point #2: "))
 (setq p3 (getpoint "Circle point #3: "))

 (setq p01 (list 0 0 0))
 (setq dx (- (car p2) (car p1)))
 (setq dy (- (cadr p2) (cadr p1)))
 (setq dz (- (caddr p2) (caddr p1)))
 (setq p02 (list dx dy dz))
 (setq dx (- (car p3) (car p1)))
 (setq dy (- (cadr p3) (cadr p1)))
 (setq dz (- (caddr p3) (caddr p1)))
 (setq p03 (list dx dy dz))
 (setq x (/ (+ (car p01) (car p02) (car p03)) 3))
 (setq y (/ (+ (cadr p01) (cadr p02) (cadr p03)) 3))
 (setq z (/ (+ (caddr p01) (caddr p02) (caddr p03)) 3))
 (setq pm (list x y z))
 (setq l (distance (list 0 0 0) pm))
 (setq glx (/ (car pm) l))
 (setq gly (/ (cadr pm) l))
 (setq glz (/ (caddr pm) l))
 (setq gl (list glx gly glz))
 (setq gx2 (* (car p02) glx))
 (setq gy2 (* (cadr p02) gly))
 (setq gz2 (* (caddr p02) glz))
 (setq lm2 (+ gx2 gy2 gz2))
 (setq gx2 (* (car p03) glx))
 (setq gy2 (* (cadr p03) gly))
 (setq gz2 (* (caddr p03) glz))
 (setq lm3 (+ gx2 gy2 gz2))
 (setq dx (* glx lm2))
 (setq dy (* gly lm2))
 (setq dz (* glz lm2))
 (setq pp2 (list dx dy dz))
 (setq dx (* glx lm3))
 (setq dy (* gly lm3))
 (setq dz (* glz lm3))
 (setq pp3 (list dx dy dz))
 (setq dx (- (car p02) (car pp2)))
 (setq dy (- (cadr p02) (cadr pp2)))
 (setq dz (- (caddr p02) (caddr pp2)))
 (setq pd2 (list dx dy dz))
 (setq dx (- (car p03) (car pp3)))
 (setq dy (- (cadr p03) (cadr pp3)))
 (setq dz (- (caddr p03) (caddr pp3)))
 (setq pd3 (list dx dy dz))
 (setq dx (- (car pd2) (car pd3)))
 (setq dy (- (cadr pd2) (cadr pd3)))
 (setq dz (- (caddr pd2) (caddr pd3)))
 (setq pd (list dx dy dz))
 (setq l (distance (list 0 0 0) pd))
 (setq gdx (/ (car pd) l))
 (setq gdy (/ (cadr pd) l))
 (setq gdz (/ (caddr pd) l))
 (setq gd (list gdx gdy gdz))
 (setq gx2 (* (car pd2) gdx))
 (setq gy2 (* (cadr pd2) gdy))
 (setq gz2 (* (caddr pd2) gdz))
 (setq dm2 (+ gx2 gy2 gz2))
 (setq gx2 (* (car pd3) gdx))
 (setq gy2 (* (cadr pd3) gdy))
 (setq gz2 (* (caddr pd3) gdz))
 (setq dm3 (+ gx2 gy2 gz2))

 (setq a1 lm2)
 (setq a2 (- lm3 lm2))
 (setq b1 dm2)
 (setq b2 (- dm3 dm2))
 (setq s1 (/ lm2 2))
 (setq s2 (/ (+ lm3 lm2) 2))
 (setq t1 (/ dm2 2))
 (setq t2 (/ (+ dm3 dm2) 2))
 (setq c1 (- 0 (+ (* a1 s1) (* b1 t1))))
 (setq c2 (- 0 (+ (* a2 s2) (* b2 t2))))
 (setq ab (- (* b1 a2) (* b2 a1)))
 (setq bc (- (* b2 c1) (* b1 c2)))
 (setq lc (/ bc ab))
 (setq dc (/ (- 0 (+ c1 (* a1 lc))) b1))
 (setq cld (list lc dc))

 (setq dxl (* glx lc))
 (setq dyl (* gly lc))
 (setq dzl (* glz lc))
 (setq pcl (list dxl dyl dzl))
 (setq dxd (* gdx dc))
 (setq dyd (* gdy dc))
 (setq dzd (* gdz dc))
 (setq pcd (list dxd dyd dzd))
 (setq x (+ dxl dxd (car p1)))
 (setq y (+ dyl dyd (cadr p1)))
 (setq z (+ dzl dzd (caddr p1)))
 (setq pc (list x y z))
 (setq r (distance pc p1))

 (princ pc)

 (command "_point" pc)
 (command "_circle" pc r)
; (command "_ellipse" "_C" pc p1 p2)
)
