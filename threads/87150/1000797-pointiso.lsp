(defun c:pointiso (/ p1 p2 dh)
  (setq p1 (getpoint "\n Point 1:"))
  (setq p2 (getpoint "\n Point 2:"))
  (setq dh (getdist "\n Step H:"))
  (setq h1 (caddr p1))
  (setq h2 (caddr p2))
  (setq l (distance p1 p2))
  (setq z0 (* (fix (/ h1 dh)) dh))
  (setq zn (* (fix (/ h2 dh)) dh))
  (setq n (/ (- zn z0) dh))
  (if (> 0 n)
    (progn
      (setq n (- 0 n))
      (setq dh (- 0 dh))
    )
  )
  (if (> n 0)
    (progn
      (setq dx (- (car p2) (car p1)))
      (setq dy (- (cadr p2) (cadr p1)))
      (setq dz (- (caddr p2) (caddr p1)))
      (setq k 0)
      (repeat n
        (setq k (+ k 1))
        (setq hn (+ z0 (* k dh)))
        (setq dhn (- hn h1))
        (setq dxn (* (/ dhn dz) dx))
        (setq dyn (* (/ dhn dz) dy))
        (setq xn (+ (car p1) dxn))
        (setq yn (+ (cadr p1) dyn))
        (setq ph (list xn yn hn))
        (setq ln (distance ph p1))
        (if (> l ln)
          (progn
            (princ ph)

            (command "_point" ph)
          )
        )
      )
    )
  )
)
